-- **********************************************************************
--      Date		: 09-2007
--      Filename	: asn1.asn
-- **********************************************************************

AirCondition DEFINITIONS IMPLICIT TAGS ::=

BEGIN


AirRecord2 ::= SEQUENCE
{
	hot 			[0] 		 BOOLEAN OPTIONAL,
	degree			[1] EXPLICIT INTEGER,
	cloud						 Cloud2,
	location  	[PRIVATE 1]		 City2,
	time		[APPLICATION 8]  Minutes2
}

Cloud2 ::=  SET {
	speed			Speed2,
	isBlue			BOOLEAN,
	parameters	[0]	IntSeq
}

IntSeq ::= SEQUENCE OF INTEGER

Speed2  ::=  OCTET STRING

City2 ::= ENUMERATED {
	istanbul 	(1),
	ankara 		(2),
	izmir	(5)
}

Minutes2 ::= INTEGER {min(0), max(59)}

-- In below example the class AvailabilityStatus.java can be generated by JAC, 
-- but it will not be filled with its elements below. 
--You should fill your SEQUENCE OF/SET OF objects by your own in these situations
--
--AvailabilityStatus ::= SEQUENCE OF INTEGER 
--{ inTest(0), failed(1), powerOff(2), offLine(3) }

END
